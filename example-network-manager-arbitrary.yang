module example-network-manager-arbitrary {
  yang-version 1.1;
  namespace "urn:example:network-manager-arbitrary";
  prefix exa;

  import ietf-inet-types {
    prefix inet;
  }
  import ietf-yang-schema-mount {
    prefix yangmnt;
  }

  container managed-devices {
    description
      "The managed devices and device communication settings.";

    list device {
      key name;
      leaf name {
        type string;
      }
      container transport {
        choice protocol {
          mandatory true;
          container netconf {
            leaf address {
              type inet:ip-address;
              mandatory true;
            }
            container authentication {
              // ...
            }
          }
          container restconf {
            leaf address {
              type inet:ip-address;
              mandatory true;
            }
            // ...
          }
        }
      }
      container root {
        yangmnt:mount-point managed-device;
      }
    }
  }
}
